module interface-reconciler {
  yang-version 1.1;
  namespace "http://cnad.dev/ns/yang/interface-reconciler";
  prefix ir;

  import tailf-common {
    prefix tailf;
  }
  import tailf-ncs {
    prefix ncs;
  }

  description
    "Thin service that owns description and/or enabled on a single interface
     of an NSO-managed device.  Committed in reconcile mode so pre-existing
     brownfield config is adopted without FASTMAP-churn on unrelated state.

     Keyed by (device, interface-name) so each adapter apply creates one
     service instance per managed (device, interface) pair and writes only
     the attributes that have accepted intent.

     The apply worker in nso-adapter/core/apply.py PUT-s/PATCH-es these
     instances via RESTCONF with the tailf:reconcile commit option.";

  revision 2026-06-01 {
    description "Phase 3 M12 B1 — add ipv4-address/ipv6-address lists and vrf leaf.";
  }

  revision 2026-05-23 {
    description "Initial version — Phase 2 M4 (Spike S2).";
  }

  list interface-config {
    description
      "One service instance = one managed interface on one device.
       The adapter creates/updates instances; NSO FASTMAP tracks them.
       Commit must use 'reconcile' so pre-existing config is adopted.";

    key "device interface-name";

    uses ncs:service-data;
    ncs:servicepoint "interface-reconciler-sp";

    leaf device {
      type leafref {
        path "/ncs:devices/ncs:device/ncs:name";
      }
      description "NSO device name (matches nso_device_name in the adapter).";
    }

    leaf interface-name {
      type string;
      description
        "NED-normalized interface name (e.g. GigabitEthernet0/0,
         GigabitEthernet0/0/0/1, Loopback0). Must match the name stored in
         the adapter's interface table.";
    }

    leaf description {
      type string;
      description
        "Interface description to deploy.  Absent leaf = do not touch
         the description on this interface.";
    }

    leaf enabled {
      type boolean;
      description
        "Interface enabled state.  true = no shutdown; false = shutdown.
         Absent leaf = do not touch the shutdown state.";
    }

    list ipv4-address {
      key "address";
      description
        "IPv4 addresses to configure on this interface.
         Empty list = do not touch any IPv4 addresses.
         Absent list (omitted in PATCH) = do not touch.";

      leaf address {
        type string;
        description "IPv4 host address without mask (e.g. 192.168.1.1).";
      }
      leaf prefix-length {
        type uint8 {
          range "0..32";
        }
        mandatory true;
        description "IPv4 prefix length (0–32).";
      }
      leaf secondary {
        type boolean;
        default false;
        description "True if this is a secondary address on the interface.";
      }
    }

    list ipv6-address {
      key "address";
      description
        "IPv6 addresses to configure on this interface.
         Empty list = do not touch any IPv6 addresses.";

      leaf address {
        type string;
        description "IPv6 host address without prefix length (e.g. 2001:db8::1).";
      }
      leaf prefix-length {
        type uint8 {
          range "0..128";
        }
        mandatory true;
        description "IPv6 prefix length (0–128).";
      }
    }

    leaf vrf {
      type string;
      description
        "VRF name to assign to this interface.
         Absent leaf = do not touch the VRF assignment.";
    }
  }
}
